FME workspace citygml2gml_Force2D.fmw

Parameters:
- DestDataset_GML =
- SourceDataset_CITYGML =
- SourceDataset_CITYGML_4 =
- SourceDataset_CITYGML_5 =

Readers:
- CITYGML_1: CITYGML from $(SourceDataset_CITYGML)
- CITYGML_2: CITYGML from $(SourceDataset_CITYGML_5)
- CITYGML_3: CITYGML from $(SourceDataset_CITYGML_4)

Writers:
- GML_1: GML to $(DestDataset_GML)

Building (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, ADMINISTRA xml_buffer, ADRESSE xml_buffer, APPDATMAX xml_buffer, APPDATMIN xml_buffer, BUILDINGID xml_buffer, CODE_DGI xml_buffer, CODE_INSEE xml_buffer, COMIDATMAX xml_buffer, COMIDATMIN xml_buffer, CULTE xml_buffer, DEPDATMAX xml_buffer, DEPDATMIN xml_buffer, ENSEIGNEME xml_buffer, MAISDATMAX xml_buffer, MAISDATMIN xml_buffer, MILLESIME xml_buffer, NBAPP xml_buffer, NBCOMIN xml_buffer, NBDEP xml_buffer, NBMAIS xml_buffer,
      NIVAPP xml_buffer, NIVCOMIN xml_buffer, NIVDEP xml_buffer, NIVMAIS xml_buffer, NOMCOMMUNE xml_buffer, NOMOFFICIE xml_buffer, Profile xml_buffer, SANTE xml_buffer, SPORT xml_buffer, SURFTOIT xml_buffer, URGENCE xml_buffer, Volume xml_buffer, ZMAXTOIT xml_buffer, ZMINTOIT xml_buffer, ZMOYTOIT xml_buffer, insee xml_buffer, nomreduit xml_buffer
    -> 2DForcer
2DForcer
    2D -> Building (writer GML_1)
Building (writer GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, ADMINISTRA xml_buffer, ADRESSE xml_buffer, APPDATMAX xml_buffer, APPDATMIN xml_buffer, BUILDINGID xml_buffer, CODE_DGI xml_buffer, CODE_INSEE xml_buffer, COMIDATMAX xml_buffer, COMIDATMIN xml_buffer, CULTE xml_buffer, DEPDATMAX xml_buffer, DEPDATMIN xml_buffer, ENSEIGNEME xml_buffer, MAISDATMAX xml_buffer, MAISDATMIN xml_buffer, MILLESIME xml_buffer, NBAPP xml_buffer, NBCOMIN xml_buffer, NBDEP xml_buffer, NBMAIS xml_buffer,
      NIVAPP xml_buffer, NIVCOMIN xml_buffer, NIVDEP xml_buffer, NIVMAIS xml_buffer, NOMCOMMUNE xml_buffer, NOMOFFICIE xml_buffer, Profile xml_buffer, SANTE xml_buffer, SPORT xml_buffer, SURFTOIT xml_buffer, URGENCE xml_buffer, Volume xml_buffer, ZMAXTOIT xml_buffer, ZMINTOIT xml_buffer, ZMOYTOIT xml_buffer, insee xml_buffer, nomreduit xml_buffer
GroundSurface (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> 2DForcer_2
2DForcer_2
    2D -> GroundSurface (writer GML_1)
GroundSurface (writer GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
RoofSurface (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> 2DForcer_3
2DForcer_3
    2D -> RoofSurface (writer GML_1)
RoofSurface (writer GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
WallSurface (reader CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
    -> 2DForcer_4
2DForcer_4
    2D -> WallSurface (writer GML_1)
WallSurface (writer GML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
